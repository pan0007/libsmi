// correct
 
// Notes:
// 1. This example test the correctness of the 'stmtsep' rule;
//

module "test13"{
        unknownstatement  dkjhf {unknownstatement  dkjhfl; }
	yang-version '1' {}
	namespace "urn:smilib:params:test9" { ext1 dkjhf; ext1 dkjhf;  } 
	unknownstatement;
	unknownstatement  dkjhf {}
 	prefix test13; 

}
